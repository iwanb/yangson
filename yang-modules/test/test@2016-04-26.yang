module test {

  yang-version "1.1";

  namespace "http://example.com/test";

  prefix "t";

  import ietf-yang-types {
    prefix "yang";
    revision-date 2013-07-15;
  }

  import defs {
    prefix "d";
    revision-date 2016-04-26;
  }

  include subtest;

  revision 2016-04-26;

  feature feA;

  feature feB;

  identity licence-property;

  identity adaptation-sharing {
    base licence-property;
  }
  identity derivatives {
    base adaptation-sharing;
  }
  identity no-derivatives {
    base adaptation-sharing;
  }
  identity share-alike {
    base adaptation-sharing;
  }

  identity permitted-uses {
    base licence-property;
  }
  identity all-uses {
    base permitted-uses;
  }
  identity non-commercial {
    base permitted-uses;
  }

  identity CC-BY {
    base derivatives;
    base all-uses;
  }

  identity CC-BY-NC {
    base derivatives;
    base non-commercial;
  }

  identity CC-BY-ND {
    base no-derivatives;
    base all-uses;
  }

  container contA {
    typedef hex-number {
      type string {
        length "1..max";
        pattern "[0-9A-Fa-f]*";
      }
      default "F00";
    }
    must "not(leafA <= leafB)";
    leaf leafA {
      type d:typA;
    }
    leaf leafB {
      type d:typA;
      config "false";
      mandatory "true";
    }
    list listA {
      key 'leafE leafF';
      unique "contD/leafG";
      min-elements 2;
      grouping grA {
        uses d:grB {
          augment "contE" {
            leaf leafP {
	      when "../leafU != 'false'";
              type uint8;
            }
          }
        }
        leaf leafGroup {
          type uint8 {
            default "10";
          }
        }
      }
      leaf leafE {
        type hex-number;
      }
      leaf leafF {
        type boolean;
        must ".";
      }
      leaf leafW {
	type d:typE;
      }
      container contD {
        leaf leafG {
          type yang:yang-identifier;
        }
        leaf leafM {
          if-feature "feB";
          type uint8;
        }
        uses grA {
          refine "contE/leafP" {
            default "42";
          }
        }
        action acA {
          output {
            leaf leafL {
              type boolean;
              mandatory "true";
            }
          }
        }
      }
    }
    anydata anydA {
      mandatory "true";
    }
    anyxml anyxA {
      description
        "A description.";
    }
  }

  container contT {
    description
      "Leafs of all types.";
    leaf int8 {
      type int8 {
        range "-100..max";
      }
    }
    leaf int16 {
      type int16;
    }
    leaf int32 {
      type int32;
    }
    leaf int64 {
      type int64;
    }
    leaf uint8 {
      type uint8 {
        range "100..200";
      }
    }
    leaf uint16 {
      type uint16;
    }
    leaf uint32 {
      type uint32;
    }
    leaf uint64 {
      type uint64;
    }
    leaf decimal64 {
      type decimal64 {
        fraction-digits "18";
        range "1..max";
      }
    }
    leaf string {
      type string {
        length "2..4 | 11 | 12";
        pattern "[a-z0-9]+\\s{1,2}[a-z]*";
        pattern "xx x.*" {
          modifier invert-match;
        }
      }
    }
    leaf boolean {
      type boolean;
      default "true";
    }
    leaf enumeration {
      type d:typC {
        enum Hearts {
          if-feature "feA and not feB";
        }
        enum Diamonds {
          if-feature "feB";
        }
	enum Clubs;
      }
    }
    leaf bits {
      type d:typD {
        bit dos {
          if-feature "feA";
        }
        bit tres {
          if-feature "feB";
        }
	bit cuatro;
      }
      default "cuatro";
    }
    leaf binary {
      type binary {
        length "1..54";
      }
    }
  }
}
